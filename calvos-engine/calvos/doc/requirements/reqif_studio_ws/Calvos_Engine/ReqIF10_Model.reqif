# ReqIF10_Model

# Specification: Requirements Document
- ReqIF.Description: SYR_Engine

## REQ-1: Title Here
- ObjectType: heading
- Maturity: NA

### REQ-2: Find engine components
Text Here
- ObjectType: comment
- Maturity: NA

#### REQ-3
The engine shall provide a function to retrieve the components defined in the engine system.
- ObjectType: functional_requirement

#### REQ-4
The engine shall identify a component if all of the following items are found within the COMPONENTS_PATH:
1. a python module with a name not starting with underscore "_", and
2. an XML component descriptor file with the same file steam name and in the same path as the python module in 1, and
3. a folder with the same name and in the same location of the python module in 1, and
4. a sub-folder within folder in 3 named "doc", and
5. a sub-folder within folder in 3 named "gen", and
6. a sub-folder within folder in 3 named "usr_in"
- ObjectType: functional_requirement

#### REQ-6
If all conditions in REQ-4 are met then the engine shall consider that it has found a component with a short name equal to the python module name in REQ-4 point 1.
- ObjectType: functional_requirement

#### REQ-8
If a component full name determined by the engine as in REQ-7 doesn't match the same component full name contained within the component's XML component descriptor file then the engine shall consider the component as a "malformed" component.
- ObjectType: functional_requirement

#### REQ-5
The engine shall iterate over all subfolders within the COMPONENTS_PATH when searching for components.
- ObjectType: functional_requirement
